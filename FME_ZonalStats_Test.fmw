FME workspace FME_ZonalStats_Test.fmw

Parameters:
- SourceDataset_SHAPE = C:\Users\zool1301\Documents\Other_Data\Moritz\dishi_v2\dishi_v2.shp   # Source Esri Shape File(s)
- Keep_Source_Attributes = True   # Keep all source attributes?
- SourceDataset_PATH = C:\Temp\pfpr_model43_outputs_tiled   # Source Folder and File Pathnames Folder
- Filename_Filter = *.tif   # Raster Filename filter (e.g. *.Data.tif)
- Stats_To_Calculate = count mean range   # Which zonal statistics should be calculated?
- UseAllTouchedPixels = False
- SourceDataset_SHAPE_5 = \\129.67.26.176\map_data\admin_units\admin2013\admin2013_1.shp   # Source Esri Shape File(s)
- SourceDataset_SHAPE_4 = \\129.67.26.176\map_data\admin_units\simplified_units_2013\admin0_simplified.shp   # Source Esri Shape File(s)
- DestDataset_CSV = C:\Temp   # Destination CSV (CommaSeparatedValue) Folder

Readers:
- SHAPE_1: SHAPE from $(SourceDataset_SHAPE)
- SHAPE_2: SHAPE from $(SourceDataset_SHAPE_5)
- SHAPE_3: SHAPE from $(SourceDataset_SHAPE_4)

Writers:
- CSV_1: CSV to $(DestDataset_CSV)

admin0_simplified (reader SHAPE_3)
    attributes: GAUL_CODE number(11,0), COUNTRY_ID char(3), NAME char(254), admin char(50), pub_name char(50)
    -> ZonalStats
Note: 41 minutes on 8000 files of PR cube and admin 0 global shapefile
ZonalStats
    Keep_Source_Attributes = $(Keep_Source_Attributes)
    UseAllTouchedPixels = $(UseAllTouchedPixels)
    Filename_Filter = $(Filename_Filter)
    Stats_To_Calculate = $(Stats_To_Calculate)
    SourceDataset_PATH = $(SourceDataset_PATH)
    -> AttributeExposer
AttributeExposer
    ATTR_LIST = mean,max,min,count
    -> ZonalStats_Output
    -> admin0_simplified (writer CSV_1)
admin0_simplified (writer CSV_1)
    attributes: GAUL_CODE number(11,0), COUNTRY_ID char(3), NAME char(254), admin char(50), pub_name char(50), rastername auto, mean auto, max auto, min auto, count auto
ZonalStats_Output: Inspector
admin2013_1 (reader SHAPE_2)
    attributes: NAME char(254), COUNTRY_ID char(50), GAUL_CODE number(9,0), ADMN_LEVEL char(1), PARENT_ID number(9,0)
dishi_v2 (reader SHAPE_1)
    attributes: ZONECODE number(8,0)

FME custom transformer ZonalStats

Parameters:
- SourceDataset_PATH = E:\MCD43B4_Gapfilled_Output\EVI\Output_Monthly_Means\5km   # Source Folder and File Pathnames Folder
- Stats_To_Calculate = count mean max   # Which zonal statistics should be calculated?
- Keep_Source_Attributes = True   # Keep all source attributes?
- Filename_Filter = *.Mean.tif   # Raster Filename filter (e.g. *.Data.tif)
- UseAllTouchedPixels = False

Features_Input (input)
    -> Counter
Note: Create an FID so that we always have one
Counter
    DOMAIN = counter
    CNT_ATTR = _FME_FID_
    SCOPE = Global
    START = 0
    -> GeometryExtractor
Note: Save geometry to a WKT attribute so the Python code can access it; give it a standard (Well Known!) name too
GeometryExtractor
    OGCVERSION = 1.1
    KIND_LONG = OGC Well Known Text
    ATTR = _FME_GEOM_WKT_
    -> PythonCaller
Creator
    GEOMTYPE = Geometry Object
    NUM = 1
    CREATED -> FeatureReader
FeatureReader
    ATTRIBUTES = PATH,"path_unix,path_windows,path_rootname,path_filename,path_extension,path_filesize,path_ownername,path_readonly,path_modified_date,path_created_date,path_accessed_date,path_directory_unix,path_directory_windows,path_type,fme_geometry{0}"
    DATASET = $(SourceDataset_PATH)
    OUTPUT_FEATURES_DISPLAY = Based on Connections
    PATH_RETRIEVE_FILE_PROPERTIES = NO
    PATH_TYPE = FILE
    ATTR_ACCUM_MODE = Only Use Result
    PATH_GLOB_PATTERN = $(Filename_Filter)
    FORMAT = PATH
    FEATURETYPES_RADIO = FEATURETYPES
    COMBINE_GEOM = Use Result
    PATH -> AttributeKeeper
AttributeKeeper
    KEEP_ATTRS = path_windows
    -> ListBuilder
ListBuilder
    LIST_NAME = RasterList
    -> PythonCaller
Note: Run zonal stats on all relevant rasters
PythonCaller
    NEW_ATTRIBUTES = rastername
    PYTHONSOURCE:
      import fme
      import fmeobjects

      try:
          from osgeo import gdal,ogr
          from osgeo.gdalnumeric import *
      except ImportError:
          import gdal,ogr
          from gdalnumeric import *

      # move existing code to module with transformer
      from raster_stats_multi import raster_stats_multi
      from rasterstats.utils import *
      from shapely.geometry import shape, box, MultiPolygon

      logger = fmeobjects.FMELogFile()

      # Template Function interface:
      def processFeature(feature):
          pass

      # Template Class Interface:
      class FeatureProcessor(object):

          def __init__(self):
              #self.allFeatures = {}
              self.allFeatures = []
              self.rasterFiles = []
              self.allIDs = set()

          # for each input feature turn it into a dictionary of attribs and save to a list
          # Except for feature which has a RasterList attribute - there must be one of these
          def input(self,feature):
              # there must be exactly one feature provided that has a RasterList{} attribute
              list = feature.getAttribute('RasterList{}.path_windows')
              if list != None:
                  if len(self.rasterFiles) != 0:
                      # throw error better
                      logger.logMessageString(
                          "Zonal stats error - more than one feature with a RasterList{} attribute"
                      )
                      assert False
                  else:
                      self.rasterFiles = list
              else:
                  #geomWKT = feature.getAttribute('_FME_GEOM_WKT_')
                  featID = feature.getAttribute('_FME_FID_')
                  if featID in self.allIDs:
                      logger.logMessageString("Non unique feature IDs!")
                      assert False
                  attrNames = feature.getAllAttributeNames()
                  item = {}
                  for attrName in attrNames:
                      item[attrName] = feature.getAttribute(attrName)

                  if item.has_key('_FME_GEOM_WKT_') and item.has_key('_FME_FID_'):
                      self.allFeatures.append(item)
                  else:
                      logger.logMessageString("Feature does not have necessary attributes!")

          # When all features have arrived, call the modified external zonal stats script
          def close(self):
              # get which stats to do from wb parameter
              try:
                  whichStats = FME_MacroValues['ZonalStats_Stats_To_Calculate']
                  # parse to listFME_MacroValues['StatsToRun']FME_MacroValues['Geom_Attr_WKT']FME_MacroValues['ID_Attr']FME_MacroValues['Keep_Source_Attrs']
              except:
                  whichStats = ['sum','mean','max','min']
              logger.logMessageString("Calculating stats:  "+str(whichStats))

              # get whether the input attributes should be copied over
              copyValues = "True" == FME_MacroValues['ZonalStats_Keep_Source_Attributes']
              logger.logMessageString("Copying attributes to output = "+str(copyValues))

              # Get the edge pixel inclusion strategy
              useAllTouched = "True" == FME_MacroValues['ZonalStats_UseAllTouchedPixels']
              logger.logMessageString("Using all touched pixels in zonal stats: "+str(useAllTouched))

              # run zonal_stats_multi script (modified from rasterstats package)
              results = raster_stats_multi(
                  self.allFeatures, self.rasterFiles,
                  '_FME_GEOM_WKT_', '_FME_FID_',
                  stats = whichStats,
                  copy_properties=copyValues,
                  all_touched=useAllTouched,
                  global_src_extent=True
                  )

              # output features with fid, mean, sum....
              for rastFileRes in results:
                  stats = rastFileRes['stats']
                  rastName = rastFileRes['rastername']
                  for zoneRastRes in stats:
                      feature = fmeobjects.FMEFeature()
                      feature.setAttribute('rastername', rastName)
                      for stat in zoneRastRes.keys():
                          try:
                              feature.setAttribute(stat, zoneRastRes[stat])
                          except:
                              logger.logMessageString("Did not understand "+str(stat)+" from raster "+rastName)
                              logger.logMessageString("Values was "+str(zoneRastRes[stat]))
                              assert False
                      self.pyoutput(feature)
              results = None
    PYTHONSYMBOL = FeatureProcessor
    -> PythonCaller_Output [off]
    -> AttributeRemover
AttributeRemover
    REMOVE_ATTRS = _FME_GEOM_WKT_
    LIST_ATTRS = RasterList{}
    -> Output (output)
Output (output)
PythonCaller_Output: Inspector [off]
